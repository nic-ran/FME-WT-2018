FME workspace Simple Server demo.fmw

Parameters:
- SourceDataset_ESRISHAPE = ""$(FME_MF_DIR)Data\ElevationModel\Contours\J10.shp" "$(FME_MF_DIR)Data\ElevationModel\Contours\J11.shp" "$(FME_MF_DIR)Data\ElevationModel\Contours\J12.shp" "$(FME_MF_DIR)Data\ElevationModel\Contours\J13.shp" "$(FME_MF_DIR)Data\ElevationModel\Contours\K2.shp" "$(FME_MF_DIR)Data\ElevationModel\Contours\K3.shp" "$(FME_MF_DIR)Data\ElevationModel\Contours\K4.shp" "$(FME_MF_DIR)Data\ElevationModel\Contours\K5.shp" "$(FME_MF_DIR)Data\ElevationModel\Contours\K10.shp" "$(FME_MF_DIR)Data\ElevationModel\Contours\K11.shp" "$(FME_MF_DIR)Data\ElevationModel\Contours\K12.shp" "$(FME_MF_DIR)Data\ElevationModel\Contours\K13.shp" "$(FME_MF_DIR)Data\ElevationModel\Contours\L1.shp" "$(FME_MF_DIR)Data\ElevationModel\Contours\L2.shp" "$(FME_MF_DIR)Data\ElevationModel\Contours\L3.shp" "$(FME_MF_DIR)Data\ElevationModel\Contours\L4.shp" "$(FME_MF_DIR)Data\ElevationModel\Contours\L5.shp" "$(FME_MF_DIR)Data\ElevationModel\Contours\L6.shp" "$(FME_MF_DIR)Data\ElevationModel\Contours\L7.shp" "$(FME_MF_DIR)Data\ElevationModel\Contours\L9.shp" "$(FME_MF_DIR)Data\ElevationModel\Contours\L10.shp" "$(FME_MF_DIR)Data\ElevationModel\Contours\L11.shp" "$(FME_MF_DIR)Data\ElevationModel\Contours\L12.shp" "$(FME_MF_DIR)Data\ElevationModel\Contours\L13.shp" "$(FME_MF_DIR)Data\ElevationModel\Contours\M1.shp" "$(FME_MF_DIR)Data\ElevationModel\Contours\M2.shp" "$(FME_MF_DIR)Data\ElevationModel\Contours\M3.shp" "$(FME_MF_DIR)Data\ElevationModel\Contours\M4.shp" "$(FME_MF_DIR)Data\ElevationModel\Contours\M5.shp" "$(FME_MF_DIR)Data\ElevationModel\Contours\M6.shp" "$(FME_MF_DIR)Data\ElevationModel\Contours\M7.shp" "$(FME_MF_DIR)Data\ElevationModel\Contours\M8.shp" "$(FME_MF_DIR)Data\ElevationModel\Contours\M9.shp" "$(FME_MF_DIR)Data\ElevationModel\Contours\M10.shp" "$(FME_MF_DIR)Data\ElevationModel\Contours\M11.shp" "$(FME_MF_DIR)Data\ElevationModel\Contours\M12.shp" "$(FME_MF_DIR)Data\ElevationModel\Contours\M13.shp" "$(FME_MF_DIR)Data\ElevationModel\Contours\N3.shp" "$(FME_MF_DIR)Data\ElevationModel\Contours\N4.shp" "$(FME_MF_DIR)Data\ElevationModel\Contours\N5.shp" "$(FME_MF_DIR)Data\ElevationModel\Contours\N6.shp" "$(FME_MF_DIR)Data\ElevationModel\Contours\N7.shp" "$(FME_MF_DIR)Data\ElevationModel\Contours\N8.shp" "$(FME_MF_DIR)Data\ElevationModel\Contours\N9.shp" "$(FME_MF_DIR)Data\ElevationModel\Contours\N10.shp" "$(FME_MF_DIR)Data\ElevationModel\Contours\N11.shp" "$(FME_MF_DIR)Data\ElevationModel\Contours\N12.shp" "$(FME_MF_DIR)Data\ElevationModel\Contours\N13.shp" "$(FME_MF_DIR)Data\ElevationModel\Contours\O4.shp" "$(FME_MF_DIR)Data\ElevationModel\Contours\O5.shp" "$(FME_MF_DIR)Data\ElevationModel\Contours\O6.shp" "$(FME_MF_DIR)Data\ElevationModel\Contours\O7.shp" "$(FME_MF_DIR)Data\ElevationModel\Contours\O8.shp" "$(FME_MF_DIR)Data\ElevationModel\Contours\O9.shp" "$(FME_MF_DIR)Data\ElevationModel\Contours\O10.shp" "$(FME_MF_DIR)Data\ElevationModel\Contours\O11.shp" "$(FME_MF_DIR)Data\ElevationModel\Contours\O12.shp" "$(FME_MF_DIR)Data\ElevationModel\Contours\O13.shp" "$(FME_MF_DIR)Data\ElevationModel\Contours\P7.shp" "$(FME_MF_DIR)Data\ElevationModel\Contours\P8.shp" "$(FME_MF_DIR)Data\ElevationModel\Contours\P9.shp" "$(FME_MF_DIR)Data\ElevationModel\Contours\P10.shp" "$(FME_MF_DIR)Data\ElevationModel\Contours\P11.shp" "$(FME_MF_DIR)Data\ElevationModel\Contours\P12.shp" "$(FME_MF_DIR)Data\ElevationModel\Contours\P13.shp" "$(FME_MF_DIR)Data\ElevationModel\Contours\Q6.shp" "$(FME_MF_DIR)Data\ElevationModel\Contours\Q7.shp" "$(FME_MF_DIR)Data\ElevationModel\Contours\Q8.shp" "$(FME_MF_DIR)Data\ElevationModel\Contours\Q9.shp" "$(FME_MF_DIR)Data\ElevationModel\Contours\Q10.shp" "$(FME_MF_DIR)Data\ElevationModel\Contours\Q11.shp" "$(FME_MF_DIR)Data\ElevationModel\Contours\Q12.shp" "$(FME_MF_DIR)Data\ElevationModel\Contours\Q13.shp" "$(FME_MF_DIR)Data\ElevationModel\Contours\R7.shp" "$(FME_MF_DIR)Data\ElevationModel\Contours\R8.shp" "$(FME_MF_DIR)Data\ElevationModel\Contours\R9.shp" "$(FME_MF_DIR)Data\ElevationModel\Contours\R10.shp" "$(FME_MF_DIR)Data\ElevationModel\Contours\R11.shp" "$(FME_MF_DIR)Data\ElevationModel\Contours\R12.shp" "$(FME_MF_DIR)Data\ElevationModel\Contours\R13.shp""   # Source Esri Shapefile(s)
- FEATURE_TYPES =
- SourceDataset_ESRISHAPE_3 = $(FME_MF_DIR)Data\NewDevelopment.zip   # Source Esri Shapefile(s)
- DestDataset_PDF = $(FME_MF_DIR)Data\Output\Training\SurfaceModel.pdf   # Destination Adobe 3D PDF File

Readers:
- ESRISHAPE_1: ESRISHAPE from $(SourceDataset_ESRISHAPE)
- ESRISHAPE_2: ESRISHAPE from $(SourceDataset_ESRISHAPE_3)

Writers:
- PDF_1: PDF to $(DestDataset_PDF)

J10 (reader ESRISHAPE_1)
    attributes: Elevation char(30), Grid char(30)
    -> ChangeDetector [ORIGINAL]
NewContours (reader ESRISHAPE_2)
    attributes: NewCont_ID short
    -> ChangeDetector [REVISED]
ChangeDetector
    BLANK_AND_MISSING_DIFFER = No
    LENIENT_MATCH = No
    MATCH = 2D
    MATCH_STRATEGY = Match Selected Attributes
    UNCHANGED -> ExpressionEvaluator
    ADDED -> NeighborFinder [BASE]
Labels (reader ESRISHAPE_2)
    attributes: Elevation char(3)
    -> NeighborFinder [CANDIDATE]
NeighborFinder
    ATTR_ACCUM_MODE = Merge Candidate
    ATTR_CONFLICT_RES = Use Base
    CANDIDATES_FIRST = No
    INSERT_VERTEX = No
    K = 1
    MAX = 5
    MODE = Bases and Candidates
    TREAT_POLYGON_AS = Lines
    MATCHED -> ExpressionEvaluator
ExpressionEvaluator
    ACTION = Overwrite Existing Attributes
    ATTRLIST = Elevation
    EXPRESSION = @Value(Elevation)*4
    -> 3DForcer
3DForcer
    KEEPZVAL = No
    ZVALATTR = @Value(Elevation)
    -> SurfaceModeller [POINTS/LINES]
SurfaceModeller
    ADDZ_TYPE = Replace Z
    DRAPE_TYPE = VERTEX
    INTERPOLATION_TYPE = AUTO
    NODATA_VALUE = -32767.0
    TOLERANCE = 1
    X_SPACING = 100.0
    Y_SPACING = 100.0
    TINSurface -> Surface (writer PDF_1)
Surface (writer PDF_1)
